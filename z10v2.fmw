FME workspace z10v2.fmw
Startup Python:
      import smtplib
      from email.mime.text import MIMEText
      from datetime import datetime
      import fme
      import ssl

      email_address = fme.macroValues['e-mail']
      powiat_name = fme.macroValues['powiat']
      print(powiat_name)
      port = 465
      smtp_server = "smtp.gmail.com"
      sender_email = fme.macroValues['e-mail']
      receiver_email = fme.macroValues['e-mail_klient']
      password = fme.macroValues['haslo']
      current_datetime = datetime.now().strftime('%Y-%m-%d %H:%M:%S')
      email_body = f'Drogi użytkowniku {sender_email}, o godzinie {current_datetime} rozpoczęto przetwarzanie danych dla gminy {powiat_name}'

      msg = MIMEText(email_body, 'plain', 'utf-8')
      context = ssl.create_default_context()
      with smtplib.SMTP_SSL(smtp_server, port, context=context) as server:
          server.login(sender_email, password)
          server.sendmail(sender_email, receiver_email, msg.as_string())
Shutdown Python:
      import smtplib
      from email.mime.text import MIMEText
      from datetime import datetime
      import fme
      import ssl

      email_address = fme.macroValues['e-mail']
      powiat_name = fme.macroValues['powiat']
      print(powiat_name)
      port = 465
      smtp_server = "smtp.gmail.com"
      sender_email = fme.macroValues['e-mail']
      receiver_email = fme.macroValues['e-mail_klient']
      password = fme.macroValues['haslo']
      current_datetime = datetime.now().strftime('%Y-%m-%d %H:%M:%S')
      email_body = f'Drogi użytkowniku {sender_email}, o godzinie {current_datetime} zakończono przetwarzanie danych dla gminy {powiat_name}'

      msg = MIMEText(email_body, 'plain', 'utf-8')
      context = ssl.create_default_context()
      with smtplib.SMTP_SSL(smtp_server, port, context=context) as server:
          server.login(sender_email, password)
          server.sendmail(sender_email, receiver_email, msg.as_string())

Parameters:
- haslo =
- powiat = powiat inowrocławski
- e-mail_klient =
- cloud_coverage = 18   # cloud coverage
- data_początkowa = 20230704000000
- data_końcowa = 20230714000000
- e-mail =   # e-mial
- SourceDataset_SHAPEFILE = $(FME_MF_DIR)powiaty.shp   # Source Esri Shapefile(s)
- DestDataset_GEOTIFF = $(FME_MF_DIR)ndvi   # Destination GeoTIFF Folder

Readers:
- SHAPEFILE_1: SHAPEFILE from $(SourceDataset_SHAPEFILE)

Writers:
- GEOTIFF_3: GEOTIFF to $(DestDataset_GEOTIFF) in EPSG:4326

Note: 3. Pobierz granice powiatów z dowolnego źródła i w dowolnym formacie.
powiaty (reader SHAPEFILE_1)
    attributes: gml_id varchar(254), JPT_SJR_KO varchar(254), JPT_POWIER varchar(254), JPT_KOD_JE varchar(254), JPT_NAZWA_ varchar(254), JPT_ORGAN_ varchar(254), JPT_JOR_ID varchar(254), WERSJA_OD varchar(254), WERSJA_DO varchar(254), WAZNY_OD varchar(254), WAZNY_DO varchar(254), JPT_KOD__1 varchar(254), JPT_NAZWA1 varchar(254), JPT_ORGAN1 varchar(254), JPT_WAZNA_ varchar(254), ID_BUFORA_ varchar(254), ID_BUFORA1 varchar(254), ID_TECHNIC varchar(254), IIP_PRZEST varchar(254), IIP_IDENTY varchar(254), IIP_WERSJA varchar(254), JPT_KJ_IIP varchar(254), JPT_KJ_I_1 varchar(254), JPT_KJ_I_2 varchar(254), JPT_OPIS varchar(254), JPT_SPS_KO varchar(254), ID_BUFOR_1 varchar(254), JPT_ID varchar(254), JPT_POWI_1 varchar(254), JPT_KJ_I_3 varchar(254),
      JPT_GEOMET varchar(254), JPT_GEOM_1 varchar(254), SHAPE_LENG varchar(254), SHAPE_AREA varchar(254), REGON varchar(254), RODZAJ varchar(254)
    -> powiaty
    -> TestFilter
powiaty: Inspector
TestFilter
    DEFAULT_VALUE = <UNFILTERED>
    PASSED_TEST_GROUP_OUTPUT = FIRST
    TEST_LIST = "BOOL_OP,OR,COMPOSITE_TEST,""""""1"""""",TEST_CLAUSE,TEST $(powiat) = @Value(JPT_NAZWA_)",__powiat_ = @Value(JPT_NAZWA_)
    __powiat_ = @Value(JPT_NAZWA_) -> TestFilter___powiat_____Value_JPT_NAZWA__
    __powiat_ = @Value(JPT_NAZWA_) -> Reprojector
    __powiat_ = @Value(JPT_NAZWA_) -> BoundingBoxReplacer
TestFilter___powiat_____Value_JPT_NAZWA__: Inspector
Note: 4. Odfiltruj tylko ten powiat, którego nazwa będzie podana w parametrze procesu.
BoundingBoxReplacer
    BOXTYPE = 2D Bounding Box
    BOX -> EarthCacheConnector
Note: 4. Za pomocą jednego z dwóch transformatorów, które znajdziesz na FME Hub, pobierz dane z / Sentinela-2 dla powiatu wskazanego w parametrze wejściowym procesu. Wykorzystaj także / parametry dotyczące pokrycia chmurami oraz daty początkową i końcową.
EarthCacheConnector
    api_key =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
    end_date = $(data_końcowa)
    interval = 30
    min_aoi_coverage_percentage = $(cloud_coverage)
    output_id = rgbn-a3e8-11e7-9793-ae4260ee3b4b
    pipeline_name = pipeline2
    start_date = $(data_początkowa)
    -> Sampler_3
    <Rejected> -> Terminator
Note: 6. Jeżeli znalezionych zostanie kilka zobrazowań to wybierz pierwsze z nich (Sampler) i oblicz / indeks NDVI. Wynik przytnij do granic powiatu, a następnie zapisz jako tif.
Sampler_3
    RATE = 1
    SAMPLE_MODE = No
    SAMPLE_TYPE_LONG = First N Features
    SAMPLED -> RasterBandSeparator
RasterBandSeparator
    BAND_INDEX_FIELD = _band_index
    PALETTE_INDEX_FIELD = _palette_index
    RASTER_INDEX_FIELD = _raster_index
    SPLIT_BY_NAME = Band and Palette
    -> TestFilter_RED
    -> TestFilter_NIR
TestFilter_RED
    DEFAULT_VALUE = <UNFILTERED>
    PASSED_TEST_GROUP_OUTPUT = FIRST
    TEST_LIST = "BOOL_OP,OR,COMPOSITE_TEST,""""""1"""""",TEST_CLAUSE,TEST @Value(_band_index) = 0",@Value(_band_index) = 0
    @Value(_band_index) = 0 -> NDVICalculator_3 [Red]
TestFilter_NIR
    DEFAULT_VALUE = <UNFILTERED>
    PASSED_TEST_GROUP_OUTPUT = FIRST
    TEST_LIST = "BOOL_OP,OR,COMPOSITE_TEST,""""""1"""""",TEST_CLAUSE,TEST @Value(_band_index) = 1",@Value(_band_index) = 1
    @Value(_band_index) = 1 -> NDVICalculator_3 [Infrared]
NDVICalculator_3
    COLORIZE = Blue-Yellow-Green Palette
    INDEXTYPE = NDVI
    SAVIADJUSTMENT = 0.5
    -> Clipper_3 [CANDIDATE]
Terminator
    MESSAGE = Translation Terminated
Reprojector
    DEST = EPSG:4326
    INTERPOLATION_TYPE_NAME = Nearest Neighbor
    RASTER_CELL_SIZE = Preserve Cells
    RASTER_TOLERANCE = 0.0
    REPROJECTED -> Clipper_3 [CLIPPER]
Clipper_3
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> RasterStatisticsCalculator_3
    INSIDE -> GEOTIFF0000 (writer GEOTIFF_3)
RasterStatisticsCalculator_3
    RASTER_LEVEL = BAND_ONLY
    RASTER_STATS = "0   MEAN   STDEV   "
    -> RasterStatisticsCalculator_3_Output
Note: 7. Dla otrzymanego wyniku NDVI w punkcie 6. Oblicz statystyki – wartość średnią i odchylenie / standardowe.
RasterStatisticsCalculator_3_Output: Inspector
GEOTIFF0000 (writer GEOTIFF_3)
