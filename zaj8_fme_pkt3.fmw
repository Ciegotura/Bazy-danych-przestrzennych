FME workspace zaj8_fme_pkt3.fmw

Parameters:
- SourceDataset_SHAPEFILE_3 = $(FME_MF_DIR)bdline_essh_gb\Data\GB\scotland_and_wales_region.shp   # Source Esri Shapefile(s)
- SourceDataset_GEOTIFF = ""$(FME_MF_DIR)ras250_gb\data\HP.tif" "$(FME_MF_DIR)ras250_gb\data\HT.tif" "$(FME_MF_DIR)ras250_gb\data\HU.tif" "$(FME_MF_DIR)ras250_gb\data\HW.tif" "$(FME_MF_DIR)ras250_gb\data\HX.tif" "$(FME_MF_DIR)ras250_gb\data\HY.tif" "$(FME_MF_DIR)ras250_gb\data\HZ.tif" "$(FME_MF_DIR)ras250_gb\data\NA.tif" "$(FME_MF_DIR)ras250_gb\data\NB.tif" "$(FME_MF_DIR)ras250_gb\data\NC.tif" "$(FME_MF_DIR)ras250_gb\data\ND.tif" "$(FME_MF_DIR)ras250_gb\data\NF.tif" "$(FME_MF_DIR)ras250_gb\data\NG.tif" "$(FME_MF_DIR)ras250_gb\data\NH.tif" "$(FME_MF_DIR)ras250_gb\data\NJ.tif" "$(FME_MF_DIR)ras250_gb\data\NK.tif" "$(FME_MF_DIR)ras250_gb\data\NL.tif" "$(FME_MF_DIR)ras250_gb\data\NM.tif" "$(FME_MF_DIR)ras250_gb\data\NN.tif" "$(FME_MF_DIR)ras250_gb\data\NO.tif" "$(FME_MF_DIR)ras250_gb\data\NR.tif" "$(FME_MF_DIR)ras250_gb\data\NS.tif" "$(FME_MF_DIR)ras250_gb\data\NT.tif" "$(FME_MF_DIR)ras250_gb\data\NU.tif" "$(FME_MF_DIR)ras250_gb\data\NW.tif" "$(FME_MF_DIR)ras250_gb\data\NX.tif" "$(FME_MF_DIR)ras250_gb\data\NY.tif" "$(FME_MF_DIR)ras250_gb\data\NZ.tif" "$(FME_MF_DIR)ras250_gb\data\OV.tif" "$(FME_MF_DIR)ras250_gb\data\SC.tif" "$(FME_MF_DIR)ras250_gb\data\SD.tif" "$(FME_MF_DIR)ras250_gb\data\SE.tif" "$(FME_MF_DIR)ras250_gb\data\SH.tif" "$(FME_MF_DIR)ras250_gb\data\SJ.tif" "$(FME_MF_DIR)ras250_gb\data\SK.tif" "$(FME_MF_DIR)ras250_gb\data\SM.tif" "$(FME_MF_DIR)ras250_gb\data\SN.tif" "$(FME_MF_DIR)ras250_gb\data\SO.tif" "$(FME_MF_DIR)ras250_gb\data\SP.tif" "$(FME_MF_DIR)ras250_gb\data\SR.tif" "$(FME_MF_DIR)ras250_gb\data\SS.tif" "$(FME_MF_DIR)ras250_gb\data\ST.tif" "$(FME_MF_DIR)ras250_gb\data\SU.tif" "$(FME_MF_DIR)ras250_gb\data\SV.tif" "$(FME_MF_DIR)ras250_gb\data\SW.tif" "$(FME_MF_DIR)ras250_gb\data\SX.tif" "$(FME_MF_DIR)ras250_gb\data\SY.tif" "$(FME_MF_DIR)ras250_gb\data\SZ.tif" "$(FME_MF_DIR)ras250_gb\data\TA.tif" "$(FME_MF_DIR)ras250_gb\data\TF.tif" "$(FME_MF_DIR)ras250_gb\data\TG.tif" "$(FME_MF_DIR)ras250_gb\data\TL.tif" "$(FME_MF_DIR)ras250_gb\data\TM.tif" "$(FME_MF_DIR)ras250_gb\data\TQ.tif" "$(FME_MF_DIR)ras250_gb\data\TR.tif" "$(FME_MF_DIR)ras250_gb\data\TV.tif""   # Source GeoTIFF File(s) or URL(s)
- DestDataset_POSTGIS = postgres5432   # Connection
- DestDataset_POSTGIS_RASTER = postgres5432   # Connection

Readers:
- SHAPEFILE_2: SHAPEFILE from $(SourceDataset_SHAPEFILE_3)
- GEOTIFF_1: GEOTIFF from $(SourceDataset_GEOTIFF)

Writers:
- POSTGIS_1: POSTGIS to $(DestDataset_POSTGIS)
- POSTGIS_RASTER_1: POSTGIS_RASTER to $(DestDataset_POSTGIS_RASTER)

Note: 3. b Spośród rastrów z ćwiczenia 2. Wybierz tylko te, które przecinają się z poligonami reprezentującymi obszar południowej Walii
scotland_and_wales_region (reader SHAPEFILE_2)
    attributes: NAME varchar(100), AREA_CODE varchar(3), DESCRIPTIO varchar(50), FILE_NAME varchar(100), NUMBER number(11,0), NUMBER0 number(11,0), POLYGON_ID number(11,0), UNIT_ID number(11,0), CODE varchar(9), HECTARES float, AREA float, TYPE_CODE varchar(2), DESCRIPT0 varchar(25), TYPE_COD0 varchar(3), DESCRIPT1 varchar(36)
    -> TestFilter
Note: 3. a Odfiltruj poligony dla południowej Walii.
TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @Value(FILE_NAME) CONTAINS SOUTH_WALES",@Value(FILE_NAME) = SOUTH_WALES
    @Value(FILE_NAME) = SOUTH_WALES -> SpatialFilter [Filter]
    @Value(FILE_NAME) = SOUTH_WALES -> TopologyBuilder
TopologyBuilder
    ALLOW_CYCLES = No
    BOUNDING_EDGES = All
    CLEANING_TOLERANCE = Automatic
    DEAGGREGATE_INPUT = Yes
    GENERATION_MODE = INTERSECT
    MAX = 0
    OVERLAPPING_MODE = No
    UNIVERSE -> TopologyBuilder_Universe
    UNIVERSE -> Clipper [CLIPPER]
TopologyBuilder_Universe: Inspector
GEOTIFF (reader GEOTIFF_1)
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Clipper [CANDIDATE]
Note: 3. c Przytnij znalezione rastry do granic poligonu.
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Clipper_Inside
    INSIDE -> Exports (writer POSTGIS_1)
    INSIDE -> Exports (writer POSTGIS_RASTER_1)
Exports (writer POSTGIS_RASTER_1)
Clipper_Inside: Inspector
Exports (writer POSTGIS_1)
